/*
 * SPDX-FileCopyrightText: 2026 Elan8
 * SPDX-License-Identifier: MIT
 *
 * Project information for the vacuum showcase.
 */
package Project {
  doc /*
    AutonomousFloorCleaningRobot: a lean showcase using the Elan8 Method folder layout and
    domain-oriented SysML names.

    Library imports (via Spec42): sysml-domain-libraries domain/technical/generic.
  */
}
