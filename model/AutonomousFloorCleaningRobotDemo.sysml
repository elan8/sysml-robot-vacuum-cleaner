/*
 * SPDX-FileCopyrightText: 2026 Elan8
 * SPDX-License-Identifier: MIT
 *
 * Owns the full-workspace import hub for demo and bootstrap loading. Depends on
 * every project package that should load as part of the canonical model. Keep
 * engineering content in the imported packages.
 */
package AutonomousFloorCleaningRobotDemo {
  private import RequirementManagement::*;
  private import MonetaryUnits::*;
  private import DesignLimits::*;
  private import StakeholderNeeds::*;
  private import SystemRequirements::*;
  private import Verification::*;
  private import AnalysisCases::*;
  private import BehaviorStates::*;
  private import ArchitectureCommon::*;
  private import PhysicalProtocols::*;
  private import FunctionalArchitecture::*;
  private import PhysicalArchitecture::*;
  private import ArchitectureAllocations::*;
  private import Architecture::*;
  private import OperationalScenarios::*;
  private import ModelViews::*;
  private import ProductContext::*;
  private import SafetyAnalysis::*;
  private import TradeStudies::*;
  private import InterfaceControl::*;
  private import FirmwareArchitecture::*;
}
