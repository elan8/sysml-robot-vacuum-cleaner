/* SPDX-FileCopyrightText: 2026 Elan8
 * SPDX-License-Identifier: MIT */
package AutonomousFloorCleaningRobotDemo {
    doc /* Navigation only: flat system packages own contracts, designs, selections and evidence.
         * The selected robot occurrence is VacuumCleanerSystem::robotSystem. */
    alias systemOfInterest for VacuumCleanerSystem::robotSystem;

    private import VacuumCleanerSystem;
    private import RobotPlatformSystem;
    private import ProductContext;
    private import StakeholderNeeds;
}
