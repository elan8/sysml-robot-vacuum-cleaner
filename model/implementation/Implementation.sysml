/*
 * SPDX-FileCopyrightText: 2026 Elan8
 * SPDX-License-Identifier: MIT
 *
 * Engineer-facing views over the canonical architecture graph. This package
 * owns no duplicate task, interface, rail, work-package, or component facts.
 */
package Implementation {
  private import Views::*;
  private import Architecture::*;
  private import PhysicalArchitecture::*;
  private import FirmwareArchitecture::*;
  private import ArchitectureAllocations::*;
  private import ElectronicsComponentSelection::*;

  part def ImplementationEngineer;
  part implementationEngineer : ImplementationEngineer;

  concern implementationHandoff {
    doc /* Which runtime, peripheral, electrical, and component facts implement the robot? */
    subject;
    stakeholder :>> implementationEngineer;
  }

  viewpoint implementationHandoffPerspective {
    frame implementationHandoff;
  }

  view softwareRuntimeHandoff : GeneralView {
    satisfy implementationHandoffPerspective;
    expose FirmwareArchitecture::FirmwareTaskArchitecture;
    expose PhysicalArchitecture::RobotFirmwareSuite;
    expose Architecture::robotSystem.physical.firmwareTasks;
    expose Architecture::robotSystem.physical.robotFirmware;
    filter @SysML::PartUsage;
  }

  view peripheralAccessHandoff : GeneralView {
    satisfy implementationHandoffPerspective;
    expose PhysicalArchitecture::AutonomousFloorCleaningRobot;
    expose FirmwareArchitecture::FirmwareTaskArchitecture::sensorAcquisition;
    expose FirmwareArchitecture::FirmwareTaskArchitecture::motorControl;
    expose FirmwareArchitecture::FirmwareTaskArchitecture::safetySupervisor;
    expose FirmwareArchitecture::FirmwareTaskArchitecture::storage;
    expose FirmwareArchitecture::FirmwareTaskArchitecture::appProtocol;
    expose PhysicalArchitecture::MainControlPcb::mcuI2cMaster;
    expose PhysicalArchitecture::MainControlPcb::wirelessUart;
    expose PhysicalArchitecture::MainControlPcb::flash;
    expose Architecture::robotSystem.physical.firmwareTasks;
    expose Architecture::robotSystem.physical.mainElectronics.mainControlPcb;
    expose Architecture::robotSystem.physical.mainElectronics.safetyGpioHarness;
    filter @SysML::PartUsage;
  }

  view electronicsInterfaceHandoff : InterconnectionView {
    satisfy implementationHandoffPerspective;
    expose Architecture::robotSystem.physical.powerModule;
    expose Architecture::robotSystem.physical.sensorAssembly;
    expose Architecture::robotSystem.physical.driveModule;
    expose Architecture::robotSystem.physical.mainElectronics;
  }

  view railBudgetHandoff : GeneralView {
    satisfy implementationHandoffPerspective;
    expose Architecture::robotSystem.physical.batteryRailBudget;
    expose Architecture::robotSystem.physical.logicRailBudget;
    expose Architecture::robotSystem.physical.sensorRailBudget;
  }

  view componentSelectionHandoff : GeneralView {
    satisfy implementationHandoffPerspective;
    expose ElectronicsComponentSelection::ElectronicsComponentSelectionBaseline;
    expose ElectronicsComponentSelection::electronicsComponentSelectionBaseline;
    expose Architecture::robotSystem.physical.mainElectronics;
    expose Architecture::robotSystem.physical.sensorAssembly;
    expose Architecture::robotSystem.physical.powerModule;
    filter @SysML::PartUsage;
  }
}
