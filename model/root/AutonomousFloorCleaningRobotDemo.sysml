/*
 * SPDX-FileCopyrightText: 2026 Elan8
 * SPDX-License-Identifier: MIT
 *
 * Full-workspace import hub for the lean showcase.
 */
package AutonomousFloorCleaningRobotDemo {
  private import VacuumCleanerQuantitiesAndUnits::*;
  private import PurchasedParts::*;
  private import DomainModel::*;
  private import DesignLimits::*;
  private import StakeholderNeeds::*;
  private import SystemRequirements::*;
  private import FunctionalArchitecture::*;
  private import BehaviorStates::*;
  private import OperationalScenarios::*;
  private import ProductContext::*;
  private import FirmwareArchitecture::*;
  private import PhysicalArchitecture::*;
  private import Architecture::*;
  private import AnalysisCases::*;
  private import Verification::*;
  private import ModelViews::*;
}
